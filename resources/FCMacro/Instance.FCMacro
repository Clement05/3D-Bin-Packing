doc = App.ActiveDocument
box2 = doc.addObject('Part::Box','BOX_2')
box2.Length = 10
box2.Width = 10
box2.Height = 10
box2.Placement.Base.x = 0
box2.Placement.Base.y = 0
box2.Placement.Base.z = 0
box4 = doc.addObject('Part::Box','BOX_4')
box4.Length = 20
box4.Width = 70
box4.Height = 10
box4.Placement.Base.x = 10
box4.Placement.Base.y = 0
box4.Placement.Base.z = 0
box6 = doc.addObject('Part::Box','BOX_6')
box6.Length = 20
box6.Width = 20
box6.Height = 20
box6.Placement.Base.x = 30
box6.Placement.Base.y = 0
box6.Placement.Base.z = 0
box11 = doc.addObject('Part::Box','BOX_11')
box11.Length = 40
box11.Width = 50
box11.Height = 30
box11.Placement.Base.x = 50
box11.Placement.Base.y = 0
box11.Placement.Base.z = 0
box8 = doc.addObject('Part::Box','BOX_8')
box8.Length = 20
box8.Width = 20
box8.Height = 20
box8.Placement.Base.x = 0
box8.Placement.Base.y = 70
box8.Placement.Base.z = 0
box1 = doc.addObject('Part::Box','BOX_1')
box1.Length = 90
box1.Width = 20
box1.Height = 30
box1.Placement.Base.x = 0
box1.Placement.Base.y = 0
box1.Placement.Base.z = 30
box9 = doc.addObject('Part::Box','BOX_9')
box9.Length = 50
box9.Width = 30
box9.Height = 50
box9.Placement.Base.x = 0
box9.Placement.Base.y = 20
box9.Placement.Base.z = 30
box7 = doc.addObject('Part::Box','BOX_7')
box7.Length = 60
box7.Width = 30
box7.Height = 50
box7.Placement.Base.x = 0
box7.Placement.Base.y = 50
box7.Placement.Base.z = 30
box5 = doc.addObject('Part::Box','BOX_5')
box5.Length = 30
box5.Width = 30
box5.Height = 30
box5.Placement.Base.x = 60
box5.Placement.Base.y = 50
box5.Placement.Base.z = 30
box10 = doc.addObject('Part::Box','BOX_10')
box10.Length = 20
box10.Width = 20
box10.Height = 20
box10.Placement.Base.x = 0
box10.Placement.Base.y = 80
box10.Placement.Base.z = 30
box3 = doc.addObject('Part::Box','BOX_3')
box3.Length = 20
box3.Width = 20
box3.Height = 20
box3.Placement.Base.x = 20
box3.Placement.Base.y = 80
box3.Placement.Base.z = 30
doc.recompute()
